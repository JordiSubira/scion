module scion-interfaces {
  yang-version 1.1;
  namespace "urn:scion:scion-interfaces";
  prefix "sc-if";

  import scion-types{
    prefix "sc-ty";
  }

  organization
    "SCION group";

  contact
  "Some contact here";

  description 
  "This module contains a collection of data defining the common 
  interface configuration within the Autonomous System (AS) devices.
  ";

  revision 2019-11-15 {
        description "First revision for proposal.";
  }

  grouping interfaces-top{
    description "Top level grouping for interfaces";
    container interfaces{
      list interface{
        description 
        "The list of interfaces on the device.

        Every interface is uniquely identified by a number. Every instance 
        must define a public underlay and a remote underlay.
        ";
        key number;

        leaf number{
          type uint16;
          mandatory true;
        }

        leaf isd-as{
          description 
          "
          The ISD-AS name identifier of the next hop.
          ";
          type sc-ty:isd-as-type;
          mandatory true;
        }

        leaf bandwidth{
          description 
          "
          The bandwith defined on the interface level
          ";
          type uint16;
        }

        leaf mtu{
          description "Maximum transmission unit for the interface";
          type uint16;
          mandatory true;
        }

        leaf link{
          description 
          "
          The type of link definition.
          ";
          reference 
            "urn:scion:scion-types";
          type sc-ty:link-type;
          mandatory true;
        }

        leaf underlay-proto {
            description 
            "
            The underlay protocol used between the two border routers on each side of the link.
            ";
            type identityref {
                base "sc-ty:underlay-proto";
            }
            mandatory true;
        }

        container public-underlay{
          description 
          "
          The public underlay defines the address and port for the given interface.
          ";
          uses sc-ty:address-port;

          must ' not(derived-from(../underlay-proto, "sc-ty:underlay-proto-ipv4")) or
                 re-match(current()/address,"(([0-9]|[1-9][0-9]|1[0-9][0-9]|2[0-4][0-9]|25[0-5])\.){3}([0-9]|[1-9][0-9]|1[0-9][0-9]|2[0-4][0-9]|25[0-5])")'
          {
                  error-message "No match between underlay-proto and address format";
          }

          must ' not(derived-from(../underlay-proto, "sc-ty:underlay-proto-ipv6")) or
                 re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
          {
                  error-message "No match between underlay-proto and public-underlay address format";
          }

        }

        container remote-underlay{
          description
          "
          The remote underlay defines the address and port on the other side
          of the link.
          ";
          uses sc-ty:address-port;

          must ' not(derived-from(../underlay-proto, "sc-ty:underlay-proto-ipv4")) or
                 re-match(current()/address,"(([0-9]|[1-9][0-9]|1[0-9][0-9]|2[0-4][0-9]|25[0-5])\.){3}([0-9]|[1-9][0-9]|1[0-9][0-9]|2[0-4][0-9]|25[0-5])")'
          {
                  error-message "No match between underlay-proto and remote-underlay address format";
          }

          must ' not(derived-from(../underlay-proto, "sc-ty:underlay-proto-ipv6")) or
                 re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
          {
                  error-message "No match between underlay-proto and public-underlay address format";
          }
        }

        container bind-underlay{
          uses sc-ty:address-port{
            refine address{
              mandatory false;
            }
            refine l4-port{
              mandatory false;
            }
          }

          must ' not(derived-from(../underlay-proto, "sc-ty:underlay-proto-ipv4")) or
                 not(current()/address) or
                 re-match(current()/address,"(([0-9]|[1-9][0-9]|1[0-9][0-9]|2[0-4][0-9]|25[0-5])\.){3}([0-9]|[1-9][0-9]|1[0-9][0-9]|2[0-4][0-9]|25[0-5])")'
          {
                  error-message "No match between underlay-proto and bind-underlay address format";
          }

          must ' not(derived-from(../underlay-proto, "sc-ty:underlay-proto-ipv6")) or
                 not(current()/address) or
                 re-match(current()/address,"((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))")'
          {
                  error-message "No match between underlay-proto and public-underlay address format";
          }
        }
        
      }//end list interfaces
    }//end container interfaces
  }
  
}
